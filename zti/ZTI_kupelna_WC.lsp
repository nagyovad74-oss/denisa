;;; ===========================================================================
;;; REKONSTRUKCIA BYTU - ZTI  |  PODORYS ROZVODOV VODY A KANALIZACIE  |  ZTI-01
;;; Vygenerovane skriptom zti/generuj_vykres.py - needitovat rucne.
;;;
;;; Pouzitie v AutoCADe:
;;;   1. APPLOAD -> nacitat tento subor (alebo pretiahnut do okna AutoCADu)
;;;   2. prikaz ZTI -> zadat bod vlozenia (Enter = 0,0)
;;;   Vysledok sa da vratit jednym Ctrl+Z (UNDO skupina). Vykres sa neuklada.
;;;   Z MCP servera / run_lisp:  (zti:kresli 0.0 0.0)
;;;
;;; Jednotky: mm (INSUNITS = 4). Tlac v M 1:25 na A3.
;;; ===========================================================================

(defun zti:p (x y) (list (+ x zti:ox) (+ y zti:oy) 0.0))
(defun zti:p2 (x y) (list (+ x zti:ox) (+ y zti:oy)))
(defun zti:em (lst) (if (not (entmake lst)) (setq zti:err (1+ zti:err))))

(defun zti:pl (lay vs cl pr)
  (zti:em
    (append
      (list '(0 . "LWPOLYLINE") '(100 . "AcDbEntity") (cons 8 lay))
      pr
      (list '(100 . "AcDbPolyline") (cons 90 (length vs)) (cons 70 cl))
      (apply 'append
        (mapcar '(lambda (v)
                   (list (cons 10 (zti:p2 (car v) (cadr v)))
                         (cons 40 (nth 3 v)) (cons 41 (nth 4 v)) (cons 42 (nth 2 v))))
                vs)))))

(defun zti:tx (lay x y h s hj vj rot / p)
  (setq p (zti:p x y))
  (zti:em
    (list '(0 . "TEXT") '(100 . "AcDbEntity") (cons 8 lay) '(100 . "AcDbText")
          (cons 10 p) (cons 40 h) (cons 1 s) (cons 50 rot) (cons 7 "ZTI")
          (cons 72 hj) (cons 11 p) '(100 . "AcDbText") (cons 73 vj))))

(defun zti:hatch (lay pts col / n edges e b)
  (setq n (length pts) edges '())
  (setq e
    (entmake
      (append
        (list '(0 . "HATCH") '(100 . "AcDbEntity") (cons 8 lay) (cons 62 col)
              '(100 . "AcDbHatch") '(10 0.0 0.0 0.0) '(210 0.0 0.0 1.0)
              '(2 . "SOLID") '(70 . 1) '(71 . 0) '(91 . 1) '(92 . 1) (cons 93 n))
        (apply 'append
          (mapcar '(lambda (a b)
                     (list '(72 . 1) (cons 10 (zti:p2 (car a) (cadr a))) (cons 11 (zti:p2 (car b) (cadr b)))))
                  pts (append (cdr pts) (list (car pts)))))
        (list '(97 . 0) '(75 . 0) '(76 . 1) '(98 . 1) (cons 10 (zti:p2 (caar pts) (cadar pts)))))))
  ;; nahradne riesenie, ak entmake HATCH zlyha: hranica + -HATCH
  (if (not e)
    (progn
      (zti:pl lay (mapcar '(lambda (p) (list (car p) (cadr p) 0.0 0.0 0.0)) pts) 1 nil)
      (setq b (entlast))
      (setvar "HPNAME" "SOLID")
      (command "_.-HATCH" "_S" b "" "")
      (if (not (eq (entlast) b))
        (progn (command "_.CHPROP" (entlast) "" "_LA" lay "_C" (itoa col) "")
               (entdel b) (setq e (entlast)))
        (setq zti:err (1+ zti:err)))))
  e)

(defun zti:dim (x1 y1 x2 y2 bx by dir)
  (command "_.DIMLINEAR" "_non" (zti:p x1 y1) "_non" (zti:p x2 y2) dir "_non" (zti:p bx by)))

(defun zti:layer (name col lw lt desc)
  (if (not (tblsearch "LAYER" name))
    (command "_.-LAYER" "_N" name ""))
  (command "_.-LAYER" "_C" (itoa col) name "_LT" lt name "_LW" lw name "")
  (if (and (tblsearch "LAYER" name) (vlax-get-acad-object))
    (vl-catch-all-apply
      '(lambda ()
         (vla-put-Description
           (vla-item (vla-get-Layers (vla-get-ActiveDocument (vlax-get-acad-object))) name)
           desc)))))

(defun zti:setup ()
  ;; textovy styl
  (if (not (tblsearch "STYLE" "ZTI"))
    (entmake '((0 . "STYLE") (100 . "AcDbSymbolTableRecord") (100 . "AcDbTextStyleTableRecord")
               (2 . "ZTI") (70 . 0) (40 . 0.0) (41 . 1.0) (50 . 0.0) (71 . 0) (42 . 2.5)
               (3 . "arial.ttf") (4 . ""))))
  ;; typy ciar vody: SV bodkociarkovana, TV dvojbodkociarkovana (vzor v mm na papieri)
  (if (not (tblsearch "LTYPE" "ZTI_BODKOCIARA"))
    (entmake '((0 . "LTYPE") (100 . "AcDbSymbolTableRecord") (100 . "AcDbLinetypeTableRecord")
               (2 . "ZTI_BODKOCIARA") (70 . 0) (3 . "SV ____ . ____ .") (72 . 65) (73 . 4) (40 . 11.0)
               (49 . 8.0) (74 . 0) (49 . -1.5) (74 . 0) (49 . 0.0) (74 . 0) (49 . -1.5) (74 . 0))))
  (if (not (tblsearch "LTYPE" "ZTI_DVOJBODKOCIARA"))
    (entmake '((0 . "LTYPE") (100 . "AcDbSymbolTableRecord") (100 . "AcDbLinetypeTableRecord")
               (2 . "ZTI_DVOJBODKOCIARA") (70 . 0) (3 . "TV ____ . . ____") (72 . 65) (73 . 6) (40 . 12.5)
               (49 . 8.0) (74 . 0) (49 . -1.5) (74 . 0) (49 . 0.0) (74 . 0) (49 . -1.5) (74 . 0)
               (49 . 0.0) (74 . 0) (49 . -1.5) (74 . 0))))

  (zti:layer "ST_STAVBA" 7 "0.50" "Continuous" "Stavebna cast")
  (zti:layer "ZTI_ZARIADOVACIE_PREDMETY" 8 "0.25" "Continuous" "Zariadovacie predmety")
  (zti:layer "ZTI_SV" 5 "0.35" "ZTI_BODKOCIARA" "ZTI - studena voda")
  (zti:layer "ZTI_TV" 1 "0.35" "ZTI_DVOJBODKOCIARA" "ZTI - tepla voda")
  (zti:layer "ZTI_KANALIZACIA" 32 "0.50" "Continuous" "ZTI - kanalizacia")
  (zti:layer "KOTY" 4 "0.18" "Continuous" "Koty")
  (zti:layer "TEXT" 7 "0.25" "Continuous" "Texty a popisy")
  (zti:layer "RAM" 7 "0.50" "Continuous" "Ram a popisove pole")

  ;; koty - styl ZTI_25 (M 1:25, sikme znacky)
  (foreach v '(("DIMSCALE" 25.0) ("DIMTXT" 1.8) ("DIMASZ" 1.5) ("DIMTSZ" 1.2) ("DIMEXE" 1.5)
               ("DIMEXO" 1.0) ("DIMGAP" 0.6) ("DIMDLE" 1.2) ("DIMDEC" 0) ("DIMTAD" 1)
               ("DIMTIH" 0) ("DIMTOH" 0) ("DIMLUNIT" 2) ("DIMZIN" 8) ("DIMATFIT" 3) ("DIMTMOVE" 0))
    (setvar (car v) (cadr v)))
  (setvar "DIMTXSTY" "ZTI")
  (if (tblsearch "DIMSTYLE" "ZTI_25")
    (command "_.-DIMSTYLE" "_S" "ZTI_25" "_Y")
    (command "_.-DIMSTYLE" "_S" "ZTI_25"))
)

(defun zti:cast0 ()
  (zti:hatch "ST_STAVBA" (list '(-150 2100) '(3850 2100) '(3850 2250) '(-150 2250)) 253)
  (zti:hatch "ST_STAVBA" (list '(-150 -100) '(0 -100) '(0 2100) '(-150 2100)) 253)
  (zti:hatch "ST_STAVBA" (list '(0 -100) '(300 -100) '(300 0) '(0 0)) 253)
  (zti:hatch "ST_STAVBA" (list '(1000 -100) '(2400 -100) '(2400 0) '(1000 0)) 253)
  (zti:hatch "ST_STAVBA" (list '(2400 -100) '(2500 -100) '(2500 2100) '(2400 2100)) 253)
  (zti:hatch "ST_STAVBA" (list '(2500 400) '(2650 400) '(2650 500) '(2500 500)) 253)
  (zti:hatch "ST_STAVBA" (list '(3250 400) '(3700 400) '(3700 500) '(3250 500)) 253)
  (zti:hatch "ST_STAVBA" (list '(3700 400) '(3850 400) '(3850 2100) '(3700 2100)) 253)
  (zti:hatch "ST_STAVBA" (list '(2800 1700) '(2850 1700) '(2850 2100) '(2800 2100)) 253)
  (zti:hatch "ST_STAVBA" (list '(2500 1700) '(2800 1700) '(2800 1750) '(2500 1750)) 253)
  (zti:pl "ST_STAVBA" (list '(300 -100 0 0 0) '(0 -100 0 0 0) '(-150 -100 0 0 0) '(-150 2100 0 0 0) '(-150 2250 0 0 0) '(3850 2250 0 0 0) '(3850 2100 0 0 0) '(3850 400 0 0 0) '(3700 400 0 0 0) '(3250 400 0 0 0) '(3250 500 0 0 0) '(3700 500 0 0 0) '(3700 2100 0 0 0) '(2850 2100 0 0 0) '(2850 1700 0 0 0) '(2800 1700 0 0 0) '(2500 1700 0 0 0) '(2500 500 0 0 0) '(2650 500 0 0 0) '(2650 400 0 0 0) '(2500 400 0 0 0) '(2500 -100 0 0 0) '(2400 -100 0 0 0) '(1000 -100 0 0 0) '(1000 0 0 0 0) '(2400 0 0 0 0) '(2400 2100 0 0 0) '(0 2100 0 0 0) '(0 0 0 0 0) '(300 0 0 0 0)) 1 (list))
  (zti:pl "ST_STAVBA" (list '(2800 1750 0 0 0) '(2800 2100 0 0 0) '(2500 2100 0 0 0) '(2500 1750 0 0 0)) 1 (list))
  (zti:hatch "ST_STAVBA" (list '(2850 1850) '(3700 1850) '(3700 2100) '(2850 2100)) 254)
  (zti:pl "ST_STAVBA" (list '(2850 1850 0 0 0) '(3700 1850 0 0 0) '(3700 2100 0 0 0) '(2850 2100 0 0 0)) 1 (list (cons 370 25)))
  (zti:hatch "ST_STAVBA" (list '(1600 2000) '(2300 2000) '(2300 650) '(2400 650) '(2400 2100) '(1600 2100)) 254)
  (zti:pl "ST_STAVBA" (list '(1600 2000 0 0 0) '(2300 2000 0 0 0) '(2300 650 0 0 0) '(2400 650 0 0 0) '(2400 2100 0 0 0) '(1600 2100 0 0 0)) 1 (list (cons 370 25)))
  (zti:hatch "ST_STAVBA" (list '(2500 950) '(2620 950) '(2620 1700) '(2500 1700)) 254)
  (zti:pl "ST_STAVBA" (list '(2500 950 0 0 0) '(2620 950 0 0 0) '(2620 1700 0 0 0) '(2500 1700 0 0 0)) 1 (list (cons 370 25)))
  (zti:pl "ST_STAVBA" (list '(2400 960 0 0 0) '(2500 960 0 0 0) '(2500 1040 0 0 0) '(2400 1040 0 0 0)) 1 (list (cons 62 1) (cons 370 25)))
  (zti:pl "ST_STAVBA" (list '(2400 960 0 0 0) '(2500 1040 0 0 0)) 0 (list (cons 62 1)))
  (zti:pl "ST_STAVBA" (list '(2400 1040 0 0 0) '(2500 960 0 0 0)) 0 (list (cons 62 1)))
  (zti:pl "ST_STAVBA" (list '(2520 1700 0 0 0) '(2600 1700 0 0 0) '(2600 1750 0 0 0) '(2520 1750 0 0 0)) 1 (list (cons 62 1) (cons 370 25)))
  (zti:pl "ST_STAVBA" (list '(2520 1700 0 0 0) '(2600 1750 0 0 0)) 0 (list (cons 62 1)))
  (zti:pl "ST_STAVBA" (list '(2520 1750 0 0 0) '(2600 1700 0 0 0)) 0 (list (cons 62 1)))
  (zti:pl "ST_STAVBA" (list '(300 -100 0 0 0) '(300 -800 0 0 0)) 0 (list (cons 370 35)))
  (zti:em (list '(0 . "ARC") (cons 8 "ST_STAVBA") (cons 10 (zti:p 300 -100)) (cons 40 700) (cons 50 4.712389) (cons 51 6.283185)))
  (zti:pl "ST_STAVBA" (list '(3250 400 0 0 0) '(3250 -200 0 0 0)) 0 (list (cons 370 35)))
  (zti:em (list '(0 . "ARC") (cons 8 "ST_STAVBA") (cons 10 (zti:p 3250 400)) (cons 40 600) (cons 50 3.141593) (cons 51 4.712389)))
  (zti:pl "ST_STAVBA" (list '(2540 1680 0 0 0) '(2760 1680 0 0 0)) 0 (list (cons 370 50)))
  (zti:pl "ZTI_ZARIADOVACIE_PREDMETY" (list '(0 1400 0 0 0) '(1600 1400 0 0 0) '(1600 2100 0 0 0) '(0 2100 0 0 0)) 1 (list))
  (zti:pl "ZTI_ZARIADOVACIE_PREDMETY" (list '(160 1460 0 0 0) '(1440 1460 0.414 0 0) '(1540 1560 0 0 0) '(1540 1940 0.414 0 0) '(1440 2040 0 0 0) '(160 2040 0.414 0 0) '(60 1940 0 0 0) '(60 1560 0.414 0 0)) 1 (list))
  (zti:em (list '(0 . "CIRCLE") (cons 8 "ZTI_ZARIADOVACIE_PREDMETY") (cons 10 (zti:p 1300 1750)) (cons 40 30)))
  (zti:pl "ZTI_ZARIADOVACIE_PREDMETY" (list '(1660 1380 0 0 0) '(2260 1380 0 0 0) '(2260 1980 0 0 0) '(1660 1980 0 0 0)) 1 (list))
  (zti:em (list '(0 . "CIRCLE") (cons 8 "ZTI_ZARIADOVACIE_PREDMETY") (cons 10 (zti:p 1960 1680)) (cons 40 220)))
  (zti:pl "ZTI_ZARIADOVACIE_PREDMETY" (list '(1850 700 0 0 0) '(2300 700 0 0 0) '(2300 1300 0 0 0) '(1850 1300 0 0 0)) 1 (list))
  (zti:em (list '(0 . "ELLIPSE") '(100 . "AcDbEntity") (cons 8 "ZTI_ZARIADOVACIE_PREDMETY") '(100 . "AcDbEllipse") (cons 10 (zti:p 2060 1000)) '(11 0 230 0.0) '(210 0.0 0.0 1.0) (cons 40 0.65) '(41 . 0.0) (cons 42 (* 2 pi))))
  (zti:pl "ZTI_ZARIADOVACIE_PREDMETY" (list '(3095 1850 0 0 0) '(3095 1490 1 0 0) '(3455 1490 0 0 0) '(3455 1850 0 0 0)) 1 (list))
  (zti:em (list '(0 . "ELLIPSE") '(100 . "AcDbEntity") (cons 8 "ZTI_ZARIADOVACIE_PREDMETY") '(100 . "AcDbEllipse") (cons 10 (zti:p 3275 1530)) '(11 0 150 0.0) '(210 0.0 0.0 1.0) (cons 40 0.75) '(41 . 0.0) (cons 42 (* 2 pi))))
  (zti:pl "ZTI_ZARIADOVACIE_PREDMETY" (list '(3175 1850 0 0 0) '(3375 1850 0 0 0) '(3375 1880 0 0 0) '(3175 1880 0 0 0)) 1 (list))
  (zti:pl "ZTI_ZARIADOVACIE_PREDMETY" (list '(3450 625 0 0 0) '(3700 625 0 0 0) '(3700 1075 0 0 0) '(3450 1075 0 0 0)) 1 (list))
  (zti:em (list '(0 . "ELLIPSE") '(100 . "AcDbEntity") (cons 8 "ZTI_ZARIADOVACIE_PREDMETY") '(100 . "AcDbEllipse") (cons 10 (zti:p 3555 850)) '(11 0 180 0.0) '(210 0.0 0.0 1.0) (cons 40 0.5) '(41 . 0.0) (cons 42 (* 2 pi))))
  (zti:em (list '(0 . "CIRCLE") (cons 8 "ZTI_KANALIZACIA") (cons 370 70) (cons 10 (zti:p 2590 2030)) (cons 40 55)))
  (zti:em (list '(0 . "CIRCLE") (cons 8 "ZTI_KANALIZACIA") (cons 10 (zti:p 2590 2030)) (cons 40 30)))
  (zti:em (list '(0 . "CIRCLE") (cons 8 "ZTI_SV") (cons 6 "Continuous") (cons 10 (zti:p 2770 1775)) (cons 40 16)))
  (zti:em (list '(0 . "CIRCLE") (cons 8 "ZTI_TV") (cons 6 "Continuous") (cons 10 (zti:p 2700 1775)) (cons 40 16)))
  (zti:em (list '(0 . "CIRCLE") (cons 8 "ZTI_TV") (cons 6 "Continuous") (cons 62 6) (cons 10 (zti:p 2640 1775)) (cons 40 12)))
  (zti:pl "ZTI_TV" (list '(2688 1798 0 0 0) '(2712 1798 0 0 0) '(2688 1822 0 0 0) '(2712 1822 0 0 0)) 1 (list (cons 6 "Continuous")))
  (zti:pl "ZTI_TV" (list '(2688 1828 0 0 0) '(2712 1828 0 0 0) '(2712 1860 0 0 0) '(2688 1860 0 0 0)) 1 (list (cons 6 "Continuous")))
  (zti:pl "ZTI_TV" (list '(2688 1828 0 0 0) '(2712 1860 0 0 0)) 0 (list (cons 6 "Continuous")))
  (zti:pl "ZTI_SV" (list '(2758 1803 0 0 0) '(2782 1803 0 0 0) '(2758 1827 0 0 0) '(2782 1827 0 0 0)) 1 (list (cons 6 "Continuous")))
  (zti:pl "ZTI_SV" (list '(2758 1840 0 0 0) '(2782 1840 0 0 0) '(2782 1880 0 0 0) '(2758 1880 0 0 0)) 1 (list (cons 6 "Continuous")))
  (zti:pl "ZTI_SV" (list '(2758 1840 0 0 0) '(2782 1880 0 0 0)) 0 (list (cons 6 "Continuous")))
  (zti:pl "ZTI_SV" (list '(2770 1775 0 0 0) '(2770 1930 0 0 0) '(2350 1930 0 0 0)) 0 (list (cons 48 (/ 25.0 (getvar "LTSCALE")))))
  (zti:pl "ZTI_SV" (list '(2350 1930 0 0 0) '(2350 2040 0 0 0) '(1525 2040 0 0 0)) 0 (list (cons 48 (/ 25.0 (getvar "LTSCALE")))))
  (zti:pl "ZTI_SV" (list '(2350 1930 0 0 0) '(2350 925 0 0 0) '(2300 925 0 0 0)) 0 (list (cons 48 (/ 25.0 (getvar "LTSCALE")))))
  (zti:pl "ZTI_SV" (list '(2350 1700 0 0 0) '(2300 1700 0 0 0)) 0 (list (cons 48 (/ 25.0 (getvar "LTSCALE")))))
  (zti:pl "ZTI_SV" (list '(2770 1930 0 0 0) '(3640 1930 0 0 0) '(3640 850 0 0 0)) 0 (list (cons 48 (/ 25.0 (getvar "LTSCALE")))))
  (zti:pl "ZTI_SV" (list '(3150 1930 0 0 0) '(3150 1890 0 0 0)) 0 (list (cons 48 (/ 25.0 (getvar "LTSCALE")))))
  (zti:pl "ZTI_TV" (list '(2700 1775 0 0 0) '(2700 1870 0 0 0) '(2320 1870 0 0 0)) 0 (list (cons 48 (/ 25.0 (getvar "LTSCALE")))))
  (zti:pl "ZTI_TV" (list '(2320 1870 0 0 0) '(2320 2010 0 0 0) '(1375 2010 0 0 0)) 0 (list (cons 48 (/ 25.0 (getvar "LTSCALE")))))
  (zti:pl "ZTI_TV" (list '(2320 1870 0 0 0) '(2320 1075 0 0 0) '(2300 1075 0 0 0)) 0 (list (cons 48 (/ 25.0 (getvar "LTSCALE")))))
  (zti:pl "ZTI_KANALIZACIA" (list '(1300 1750 0 0 0) '(1300 2060 0 0 0) '(2370 2060 0 0 0) '(2370 1000 0 0 0) '(2560 1000 0 0 0) '(2560 1984 0 0 0)) 0 (list))
  (zti:pl "ZTI_KANALIZACIA" (list '(2300 1600 0 0 0) '(2370 1600 0 0 0)) 0 (list))
  (zti:pl "ZTI_KANALIZACIA" (list '(2300 1000 0 0 0) '(2370 1000 0 0 0)) 0 (list))
  (zti:pl "ZTI_KANALIZACIA" (list '(3680 850 0 0 0) '(3680 2010 0 0 0) '(3275 2010 0 0 0)) 0 (list))
  (zti:pl "ZTI_KANALIZACIA" (list '(3275 2010 0 0 0) '(2641 2010 0 0 0)) 0 (list (cons 370 70)))
  (zti:pl "ZTI_SV" (list '(1517.5 2040 1 15 15) '(1532.5 2040 1 15 15)) 1 (list (cons 6 "Continuous")))
  (zti:pl "ZTI_TV" (list '(1367.5 2010 1 15 15) '(1382.5 2010 1 15 15)) 1 (list (cons 6 "Continuous")))
  (zti:em (list '(0 . "CIRCLE") (cons 8 "ZTI_KANALIZACIA") (cons 10 (zti:p 1300 1750)) (cons 40 20)))
  (zti:pl "ZTI_SV" (list '(2292.5 1700 1 15 15) '(2307.5 1700 1 15 15)) 1 (list (cons 6 "Continuous")))
  (zti:em (list '(0 . "CIRCLE") (cons 8 "ZTI_KANALIZACIA") (cons 10 (zti:p 2300 1600)) (cons 40 20)))
  (zti:pl "ZTI_SV" (list '(2292.5 925 1 15 15) '(2307.5 925 1 15 15)) 1 (list (cons 6 "Continuous")))
  (zti:pl "ZTI_TV" (list '(2292.5 1075 1 15 15) '(2307.5 1075 1 15 15)) 1 (list (cons 6 "Continuous")))
  (zti:em (list '(0 . "CIRCLE") (cons 8 "ZTI_KANALIZACIA") (cons 10 (zti:p 2300 1000)) (cons 40 20)))
  (zti:pl "ZTI_SV" (list '(3142.5 1890 1 15 15) '(3157.5 1890 1 15 15)) 1 (list (cons 6 "Continuous")))
  (zti:pl "ZTI_SV" (list '(3632.5 850 1 15 15) '(3647.5 850 1 15 15)) 1 (list (cons 6 "Continuous")))
  (zti:em (list '(0 . "CIRCLE") (cons 8 "ZTI_KANALIZACIA") (cons 10 (zti:p 3680 850)) (cons 40 20)))
  (zti:pl "ZTI_KANALIZACIA" (list '(1895 2060 0 40 0) '(2005 2060 0 0 0)) 0 (list))
  (zti:pl "ZTI_KANALIZACIA" (list '(2370 1505 0 40 0) '(2370 1395 0 0 0)) 0 (list))
  (zti:pl "ZTI_KANALIZACIA" (list '(2560 1245 0 40 0) '(2560 1355 0 0 0)) 0 (list))
  (zti:pl "ZTI_KANALIZACIA" (list '(2985 2010 0 40 0) '(2875 2010 0 0 0)) 0 (list))
  (zti:pl "ZTI_KANALIZACIA" (list '(3680 1295 0 40 0) '(3680 1405 0 0 0)) 0 (list))
  (zti:pl "TEXT" (list '(1630 2060 0 0 0) '(1630 1340 0 0 0) '(2395 1340 0 0 0)) 0 (list (cons 370 18)))
  (zti:pl "TEXT" (list '(1624.5 2010 1 11 11) '(1635.5 2010 1 11 11)) 1 (list))
  (zti:pl "TEXT" (list '(1624.5 2040 1 11 11) '(1635.5 2040 1 11 11)) 1 (list))
  (zti:pl "TEXT" (list '(1624.5 2060 1 11 11) '(1635.5 2060 1 11 11)) 1 (list))
  (zti:pl "TEXT" (list '(2314.5 1340 1 11 11) '(2325.5 1340 1 11 11)) 1 (list))
  (zti:pl "TEXT" (list '(2344.5 1340 1 11 11) '(2355.5 1340 1 11 11)) 1 (list))
  (zti:pl "TEXT" (list '(2364.5 1340 1 11 11) '(2375.5 1340 1 11 11)) 1 (list))
  (zti:pl "TEXT" (list '(1630 1340 0 0 0) '(880 1340 0 0 0)) 0 (list (cons 370 18)))
  (zti:tx "TEXT" 900 1260 45 "SV 20\\U+00D72,8 PPR PN20" 0 0 0.000000)
  (zti:tx "TEXT" 900 1180 45 "TV 20\\U+00D72,8 PPR PN20" 0 0 0.000000)
  (zti:tx "TEXT" 900 1100 45 "K DN50 PP-HT, i = 2 %" 0 0 0.000000)
  (zti:tx "TEXT" 900 1020 45 "spolo\\U+010Dn\\U+00E9 V + PR + U1" 0 0 0.000000)
  (zti:pl "TEXT" (list '(3040 2010 0 0 0) '(3040 1440 0 0 0) '(2680 1440 0 0 0)) 0 (list (cons 370 18)))
  (zti:pl "TEXT" (list '(3034.5 1930 1 11 11) '(3045.5 1930 1 11 11)) 1 (list))
  (zti:pl "TEXT" (list '(3034.5 2010 1 11 11) '(3045.5 2010 1 11 11)) 1 (list))
  (zti:tx "TEXT" 2680 1360 45 "SV 20\\U+00D72,8" 0 0 0.000000)
  (zti:tx "TEXT" 2680 1280 45 "K DN100, i = 2 %" 0 0 0.000000)
  (zti:pl "TEXT" (list '(2450 1930 0 0 0) '(2450 1190 0 0 0) '(2680 1190 0 0 0)) 0 (list (cons 370 18)))
  (zti:pl "TEXT" (list '(2444.5 1930 1 11 11) '(2455.5 1930 1 11 11)) 1 (list))
  (zti:pl "TEXT" (list '(2444.5 1870 1 11 11) '(2455.5 1870 1 11 11)) 1 (list))
  (zti:tx "TEXT" 2690 1190 45 "SV/TV 25\\U+00D73,5" 0 2 0.000000)
  (zti:pl "TEXT" (list '(2560 1110 0 0 0) '(2680 1110 0 0 0)) 0 (list (cons 370 18)))
  (zti:pl "TEXT" (list '(2554.5 1110 1 11 11) '(2565.5 1110 1 11 11)) 1 (list))
  (zti:tx "TEXT" 2690 1110 45 "K DN50 z k\\U+00FApe\\U+013Ene" 0 2 0.000000)
  (zti:tx "TEXT" 2690 1040 35 "v boxe 120\\U+00D7150 nad podlahou" 0 2 0.000000)
  (zti:tx "TEXT" 2380 880 35 "P1" 1 0 0.000000)
  (zti:tx "TEXT" 2640 1560 35 "P2" 0 0 0.000000)
  (zti:tx "TEXT" 3622 1110 35 "SV 20\\U+00D72,8" 0 0 1.570796)
  (zti:tx "TEXT" 3567 1110 35 "K DN50, i = 2 %" 0 0 1.570796)
  (zti:tx "TEXT" 2700 2055 35 "K1" 0 0 0.000000)
  (zti:tx "TEXT" 2640 1625 35 "C" 1 0 0.000000)
  (zti:tx "TEXT" 2700 1625 35 "TV" 1 0 0.000000)
  (zti:tx "TEXT" 2770 1625 35 "SV" 1 0 0.000000)
  (zti:tx "TEXT" 2640 1480 45 "\\U+01601, RD 300\\U+00D7300" 0 0 0.000000)
  (zti:tx "TEXT" 800 1700 70 "V" 1 2 0.000000)
  (zti:tx "TEXT" 1870 1650 70 "PR" 1 2 0.000000)
  (zti:tx "TEXT" 2060 960 70 "U1" 1 2 0.000000)
  (zti:tx "TEXT" 3275 1765 70 "WC" 1 2 0.000000)
  (zti:tx "TEXT" 3540 820 70 "U2" 1 2 0.000000)
  (zti:tx "TEXT" 2060 1780 35 "PV" 1 0 0.000000)
  (zti:tx "TEXT" 2060 1530 35 "ZS" 1 0 0.000000)
  (zti:pl "TEXT" (list '(2090 1800 0 0 0) '(2300 1700 0 0 0)) 0 (list (cons 370 18)))
  (zti:pl "TEXT" (list '(2090 1550 0 0 0) '(2300 1600 0 0 0)) 0 (list (cons 370 18)))
  (zti:tx "TEXT" 400 820 87.5 "1.01 K\\U+00DAPE\\U+013D\\U+0147A" 0 0 0.000000)
  (zti:tx "TEXT" 400 720 45 "A = 5,04 m\\U+00B2   sv. v. 2600" 0 0 0.000000)
  (zti:tx "TEXT" 2680 860 87.5 "1.02 WC" 0 0 0.000000)
  (zti:tx "TEXT" 2680 760 45 "A = 1,92 m\\U+00B2   sv. v. 2600" 0 0 0.000000)
  (zti:tx "TEXT" 1700 -500 62.5 "CHODBA" 1 0 0.000000)
  (zti:tx "TEXT" -150 -1500 112.5 "P\\U+00D4DORYS \\U+2013 K\\U+00DAPE\\U+013D\\U+0147A 1.01 A WC 1.02" 0 0 0.000000)
  (zti:tx "TEXT" 3850 -1500 87.5 "M 1:25" 2 0 0.000000)
  (zti:pl "TEXT" (list '(-150 -1560 0 0 0) '(3850 -1560 0 0 0)) 0 (list (cons 370 50)))
  (zti:tx "TEXT" -150 -1700 45 "\\U+00B10,000 = \\U+00FArove\\U+0148 \\U+010Distej podlahy. Rozmery v mm." 0 0 0.000000)
  (zti:pl "RAM" (list '(-1500 -2600 0 0 0) '(9000 -2600 0 0 0) '(9000 4825 0 0 0) '(-1500 4825 0 0 0)) 1 (list (cons 370 18)))
  (zti:pl "RAM" (list '(-1000 -2475 0 0 0) '(8875 -2475 0 0 0) '(8875 4700 0 0 0) '(-1000 4700 0 0 0)) 1 (list (cons 370 50)))
  (zti:pl "RAM" (list '(4375 -2475 0 0 0) '(8875 -2475 0 0 0) '(8875 -1175 0 0 0) '(4375 -1175 0 0 0)) 1 (list (cons 370 50)))
  (zti:pl "RAM" (list '(4375 -2125 0 0 0) '(8875 -2125 0 0 0)) 0 (list (cons 370 35)))
  (zti:pl "RAM" (list '(4375 -1675 0 0 0) '(8875 -1675 0 0 0)) 0 (list (cons 370 35)))
  (zti:pl "RAM" (list '(4375 -1425 0 0 0) '(8875 -1425 0 0 0)) 0 (list (cons 370 35)))
  (zti:pl "RAM" (list '(6625 -1425 0 0 0) '(6625 -1175 0 0 0)) 0 (list (cons 370 18)))
  (zti:pl "RAM" (list '(6625 -1675 0 0 0) '(6625 -1675 0 0 0)) 0 (list (cons 370 18)))
  (zti:tx "TEXT" 4415 -2215 35 "STUPE\\U+0147" 0 0 0.000000)
  (zti:tx "TEXT" 4825 -2405 70 "\\U+2014" 1 0 0.000000)
  (zti:pl "RAM" (list '(5275 -2475 0 0 0) '(5275 -2125 0 0 0)) 0 (list (cons 370 18)))
  (zti:tx "TEXT" 5315 -2215 35 "MIERKA" 0 0 0.000000)
  (zti:tx "TEXT" 5725 -2405 70 "1:25" 1 0 0.000000)
  (zti:pl "RAM" (list '(6175 -2475 0 0 0) '(6175 -2125 0 0 0)) 0 (list (cons 370 18)))
  (zti:tx "TEXT" 6215 -2215 35 "FORM\\U+00C1T" 0 0 0.000000)
  (zti:tx "TEXT" 6625 -2405 70 "A3" 1 0 0.000000)
)
(defun zti:cast1 ()
  (zti:pl "RAM" (list '(7075 -2475 0 0 0) '(7075 -2125 0 0 0)) 0 (list (cons 370 18)))
  (zti:tx "TEXT" 7115 -2215 35 "D\\U+00C1TUM" 0 0 0.000000)
  (zti:tx "TEXT" 7525 -2405 70 "10/2026" 1 0 0.000000)
  (zti:pl "RAM" (list '(7975 -2475 0 0 0) '(7975 -2125 0 0 0)) 0 (list (cons 370 18)))
  (zti:tx "TEXT" 8015 -2215 35 "\\U+010C. V\\U+00DDKRESU" 0 0 0.000000)
  (zti:tx "TEXT" 8425 -2405 70 "ZTI-01" 1 0 0.000000)
  (zti:tx "TEXT" 4435 -1865 125 "REKON\\U+0160TRUKCIA BYTU \\U+2013 ZTI" 0 0 0.000000)
  (zti:tx "TEXT" 4435 -2045 70 "P\\U+00D4DORYS ROZVODOV VODY A KANALIZ\\U+00C1CIE" 0 0 0.000000)
  (zti:tx "TEXT" 4415 -1250 35 "INVESTOR" 0 0 0.000000)
  (zti:tx "TEXT" 4415 -1385 50 "\\U+2014 (doplni\\U+0165)" 0 0 0.000000)
  (zti:tx "TEXT" 6665 -1250 35 "MIESTO STAVBY" 0 0 0.000000)
  (zti:tx "TEXT" 6665 -1385 50 "3-izbov\\U+00FD byt \\U+2014 (adresa doplni\\U+0165)" 0 0 0.000000)
  (zti:tx "TEXT" 4415 -1500 35 "VYPRACOVALA" 0 0 0.000000)
  (zti:tx "TEXT" 4415 -1635 50 "\\U+2014" 0 0 0.000000)
  (zti:tx "TEXT" 6665 -1500 35 "ZODP. PROJEKTANT" 0 0 0.000000)
  (zti:tx "TEXT" 6665 -1635 50 "\\U+2014" 0 0 0.000000)
  (zti:tx "TEXT" 8835 -1635 35 "PROFESIA: ZTI" 2 0 0.000000)
  (zti:tx "TEXT" 4525 4520 87.5 "LEGENDA ZNA\\U+010CIEK" 0 0 0.000000)
  (zti:pl "TEXT" (list '(4525 4480 0 0 0) '(7125 4480 0 0 0)) 0 (list (cons 370 35)))
  (zti:pl "ZTI_SV" (list '(4525 4300 0 0 0) '(5125 4300 0 0 0)) 0 (list (cons 48 (/ 25.0 (getvar "LTSCALE")))))
  (zti:tx "TEXT" 5275 4300 45 "STUDEN\\U+00C1 VODA \\U+2013 SV, PPR PN20" 0 2 0.000000)
  (zti:pl "ZTI_TV" (list '(4525 4135 0 0 0) '(5125 4135 0 0 0)) 0 (list (cons 48 (/ 25.0 (getvar "LTSCALE")))))
  (zti:tx "TEXT" 5275 4135 45 "TEPL\\U+00C1 VODA \\U+2013 TV, PPR PN20" 0 2 0.000000)
  (zti:pl "ZTI_KANALIZACIA" (list '(4525 3970 0 0 0) '(5125 3970 0 0 0)) 0 (list))
  (zti:tx "TEXT" 5275 3970 45 "KANALIZ\\U+00C1CIA \\U+2013 PRIPOJOVACIE POTRUBIE K, PP-HT" 0 2 0.000000)
  (zti:em (list '(0 . "CIRCLE") (cons 8 "ZTI_KANALIZACIA") (cons 370 70) (cons 10 (zti:p 4825 3805)) (cons 40 55)))
  (zti:em (list '(0 . "CIRCLE") (cons 8 "ZTI_KANALIZACIA") (cons 10 (zti:p 4825 3805)) (cons 40 30)))
  (zti:tx "TEXT" 5275 3805 45 "K1 \\U+2013 KANALIZA\\U+010CN\\U+00C1 ST\\U+00DAPA\\U+010CKA DN100 (EXIST.)" 0 2 0.000000)
  (zti:em (list '(0 . "CIRCLE") (cons 8 "ZTI_SV") (cons 6 "Continuous") (cons 10 (zti:p 4675 3640)) (cons 40 16)))
  (zti:em (list '(0 . "CIRCLE") (cons 8 "ZTI_TV") (cons 6 "Continuous") (cons 10 (zti:p 4825 3640)) (cons 40 16)))
  (zti:em (list '(0 . "CIRCLE") (cons 8 "ZTI_TV") (cons 6 "Continuous") (cons 62 6) (cons 10 (zti:p 4975 3640)) (cons 40 12)))
  (zti:tx "TEXT" 5275 3640 45 "ST\\U+00DAPA\\U+010CKY SV / TV / C V \\U+0160ACHTE (EXIST.)" 0 2 0.000000)
  (zti:pl "ZTI_SV" (list '(4525 3475 0 0 0) '(4825 3475 0 0 0)) 0 (list (cons 6 "Continuous")))
  (zti:pl "ZTI_SV" (list '(4817.5 3475 1 15 15) '(4832.5 3475 1 15 15)) 1 (list (cons 6 "Continuous")))
  (zti:tx "TEXT" 5275 3475 45 "V\\U+00DDVOD VODY PRE ZARIA\\U+010EOVAC\\U+00CD PREDMET" 0 2 0.000000)
  (zti:pl "ZTI_KANALIZACIA" (list '(4845 3310 0 0 0) '(5125 3310 0 0 0)) 0 (list))
  (zti:em (list '(0 . "CIRCLE") (cons 8 "ZTI_KANALIZACIA") (cons 10 (zti:p 4825 3310)) (cons 40 20)))
  (zti:tx "TEXT" 5275 3310 45 "ZA\\U+00DASTENIE ODPADU ZARIA\\U+010EOVACIEHO PREDMETU" 0 2 0.000000)
  (zti:pl "ZTI_SV" (list '(4525 3145 0 0 0) '(5125 3145 0 0 0)) 0 (list (cons 6 "Continuous")))
  (zti:pl "ZTI_SV" (list '(4813 3133 0 0 0) '(4813 3157 0 0 0) '(4837 3133 0 0 0) '(4837 3157 0 0 0)) 1 (list (cons 6 "Continuous")))
  (zti:tx "TEXT" 5275 3145 45 "GU\\U+013DOV\\U+00DD UZ\\U+00C1VER" 0 2 0.000000)
  (zti:pl "ZTI_SV" (list '(4525 2980 0 0 0) '(4805 2980 0 0 0)) 0 (list (cons 6 "Continuous")))
  (zti:pl "ZTI_SV" (list '(4845 2980 0 0 0) '(5125 2980 0 0 0)) 0 (list (cons 6 "Continuous")))
  (zti:pl "ZTI_SV" (list '(4805 2968 0 0 0) '(4845 2968 0 0 0) '(4845 2992 0 0 0) '(4805 2992 0 0 0)) 1 (list (cons 6 "Continuous")))
  (zti:pl "ZTI_SV" (list '(4805 2968 0 0 0) '(4845 2992 0 0 0)) 0 (list (cons 6 "Continuous")))
  (zti:tx "TEXT" 5275 2980 45 "BYTOV\\U+00DD VODOMER" 0 2 0.000000)
  (zti:pl "ZTI_KANALIZACIA" (list '(4525 2815 0 0 0) '(5125 2815 0 0 0)) 0 (list))
  (zti:pl "ZTI_KANALIZACIA" (list '(4770 2815 0 40 0) '(4880 2815 0 0 0)) 0 (list))
  (zti:tx "TEXT" 5275 2815 45 "SMER SP\\U+00C1DU KANALIZ\\U+00C1CIE" 0 2 0.000000)
  (zti:hatch "ST_STAVBA" (list '(4525 2600) '(5125 2600) '(5125 2700) '(4525 2700)) 253)
  (zti:pl "ST_STAVBA" (list '(4525 2600 0 0 0) '(5125 2600 0 0 0) '(5125 2700 0 0 0) '(4525 2700 0 0 0)) 1 (list))
  (zti:tx "TEXT" 5275 2650 45 "STAVEBN\\U+00C1 KON\\U+0160TRUKCIA (EXIST.)" 0 2 0.000000)
  (zti:hatch "ST_STAVBA" (list '(4525 2435) '(5125 2435) '(5125 2535) '(4525 2535)) 254)
  (zti:pl "ST_STAVBA" (list '(4525 2435 0 0 0) '(5125 2435 0 0 0) '(5125 2535 0 0 0) '(4525 2535 0 0 0)) 1 (list (cons 370 25)))
  (zti:tx "TEXT" 5275 2485 45 "IN\\U+0160TALA\\U+010CN\\U+00C1 PREDSTENA / PREDSTIENKA SDK, OBKLADOV\\U+00DD BOX" 0 2 0.000000)
  (zti:pl "ST_STAVBA" (list '(4775 2280 0 0 0) '(4875 2280 0 0 0) '(4875 2360 0 0 0) '(4775 2360 0 0 0)) 1 (list (cons 62 1) (cons 370 25)))
  (zti:pl "ST_STAVBA" (list '(4775 2280 0 0 0) '(4875 2360 0 0 0)) 0 (list (cons 62 1)))
  (zti:pl "ST_STAVBA" (list '(4775 2360 0 0 0) '(4875 2280 0 0 0)) 0 (list (cons 62 1)))
  (zti:tx "TEXT" 5275 2320 45 "P1, P2 \\U+2013 PRIERAZ \\U+00D880 PRE POTRUBIE K DN50" 0 2 0.000000)
  (zti:tx "TEXT" 4825 2155 56 "U1" 1 2 0.000000)
  (zti:tx "TEXT" 5275 2155 45 "V, PR, U1, WC, U2 \\U+2013 OZNA\\U+010CENIE ZARIA\\U+010EOVACIEHO PREDMETU" 0 2 0.000000)
  (zti:tx "TEXT" 4825 1990 35 "PV / ZS" 1 2 0.000000)
  (zti:tx "TEXT" 5275 1990 45 "PV / ZS \\U+2013 PR\\U+00C1\\U+010CKOV\\U+00DD VENTIL / Z\\U+00C1PACHOV\\U+00C1 UZ\\U+00C1VIERKA PR\\U+00C1\\U+010CKY" 0 2 0.000000)
  (zti:pl "ST_STAVBA" (list '(4675 1825 0 0 0) '(4975 1825 0 0 0)) 0 (list (cons 370 50)))
  (zti:tx "TEXT" 5275 1825 45 "\\U+01601 \\U+2013 IN\\U+0160TALA\\U+010CN\\U+00C1 \\U+0160ACHTA, RD \\U+2013 REV\\U+00CDZNE DVIERKA 300\\U+00D7300" 0 2 0.000000)
  (zti:tx "TEXT" 4525 1565 87.5 "TECHNICK\\U+00C1 LEGENDA" 0 0 0.000000)
  (zti:pl "TEXT" (list '(4525 1525 0 0 0) '(7125 1525 0 0 0)) 0 (list (cons 370 35)))
  (zti:pl "TEXT" (list '(4525 1445 0 0 0) '(8815 1445 0 0 0)) 0 (list (cons 370 35)))
  (zti:pl "TEXT" (list '(4525 1340 0 0 0) '(8815 1340 0 0 0)) 0 (list (cons 370 35)))
  (zti:pl "TEXT" (list '(4525 1235 0 0 0) '(8815 1235 0 0 0)) 0 (list (cons 370 18)))
  (zti:pl "TEXT" (list '(4525 1130 0 0 0) '(8815 1130 0 0 0)) 0 (list (cons 370 18)))
  (zti:pl "TEXT" (list '(4525 1025 0 0 0) '(8815 1025 0 0 0)) 0 (list (cons 370 18)))
  (zti:pl "TEXT" (list '(4525 920 0 0 0) '(8815 920 0 0 0)) 0 (list (cons 370 18)))
  (zti:pl "TEXT" (list '(4525 815 0 0 0) '(8815 815 0 0 0)) 0 (list (cons 370 35)))
  (zti:pl "TEXT" (list '(4525 1445 0 0 0) '(4525 815 0 0 0)) 0 (list (cons 370 18)))
  (zti:pl "TEXT" (list '(4755 1445 0 0 0) '(4755 815 0 0 0)) 0 (list (cons 370 18)))
  (zti:pl "TEXT" (list '(6025 1445 0 0 0) '(6025 815 0 0 0)) 0 (list (cons 370 18)))
  (zti:pl "TEXT" (list '(6475 1445 0 0 0) '(6475 815 0 0 0)) 0 (list (cons 370 18)))
  (zti:pl "TEXT" (list '(6925 1445 0 0 0) '(6925 815 0 0 0)) 0 (list (cons 370 18)))
  (zti:pl "TEXT" (list '(7375 1445 0 0 0) '(7375 815 0 0 0)) 0 (list (cons 370 18)))
  (zti:pl "TEXT" (list '(8815 1445 0 0 0) '(8815 815 0 0 0)) 0 (list (cons 370 18)))
  (zti:tx "TEXT" 4555 1392.5 35 "OZN." 0 2 0.000000)
  (zti:tx "TEXT" 4785 1392.5 35 "ZARIA\\U+010EOVAC\\U+00CD PREDMET" 0 2 0.000000)
  (zti:tx "TEXT" 6055 1392.5 35 "SV" 0 2 0.000000)
  (zti:tx "TEXT" 6505 1392.5 35 "TV" 0 2 0.000000)
  (zti:tx "TEXT" 6955 1392.5 35 "K" 0 2 0.000000)
  (zti:tx "TEXT" 7405 1392.5 35 "V\\U+00DD\\U+0160KY V\\U+00DDVODOV OD \\U+00B10,000" 0 2 0.000000)
  (zti:tx "TEXT" 4555 1287.5 35 "V" 0 2 0.000000)
  (zti:tx "TEXT" 4785 1287.5 35 "VA\\U+0147A 1600\\U+00D7700" 0 2 0.000000)
  (zti:tx "TEXT" 6055 1287.5 35 "20\\U+00D72,8" 0 2 0.000000)
  (zti:tx "TEXT" 6505 1287.5 35 "20\\U+00D72,8" 0 2 0.000000)
  (zti:tx "TEXT" 6955 1287.5 35 "DN50" 0 2 0.000000)
  (zti:tx "TEXT" 7405 1287.5 35 "bat\\U+00E9ria +800, os odtoku +130" 0 2 0.000000)
  (zti:tx "TEXT" 4555 1182.5 35 "PR" 0 2 0.000000)
  (zti:tx "TEXT" 4785 1182.5 35 "PR\\U+00C1\\U+010CKA 600\\U+00D7600" 0 2 0.000000)
  (zti:tx "TEXT" 6055 1182.5 35 "20\\U+00D72,8" 0 2 0.000000)
  (zti:tx "TEXT" 6505 1182.5 35 "\\U+2014" 0 2 0.000000)
  (zti:tx "TEXT" 6955 1182.5 35 "DN50" 0 2 0.000000)
  (zti:tx "TEXT" 7405 1182.5 35 "PV +1000, ZS +700" 0 2 0.000000)
  (zti:tx "TEXT" 4555 1077.5 35 "U1" 0 2 0.000000)
  (zti:tx "TEXT" 4785 1077.5 35 "UM\\U+00DDVADLO 600" 0 2 0.000000)
  (zti:tx "TEXT" 6055 1077.5 35 "20\\U+00D72,8" 0 2 0.000000)
  (zti:tx "TEXT" 6505 1077.5 35 "20\\U+00D72,8" 0 2 0.000000)
  (zti:tx "TEXT" 6955 1077.5 35 "DN50" 0 2 0.000000)
  (zti:tx "TEXT" 7405 1077.5 35 "SV/TV +550, K +500" 0 2 0.000000)
  (zti:tx "TEXT" 4555 972.5 35 "WC" 0 2 0.000000)
  (zti:tx "TEXT" 4785 972.5 35 "Z\\U+00C1VESN\\U+00C9 WC, modul v predstene" 0 2 0.000000)
  (zti:tx "TEXT" 6055 972.5 35 "20\\U+00D72,8" 0 2 0.000000)
  (zti:tx "TEXT" 6505 972.5 35 "\\U+2014" 0 2 0.000000)
  (zti:tx "TEXT" 6955 972.5 35 "DN100" 0 2 0.000000)
  (zti:tx "TEXT" 7405 972.5 35 "SV v module, K +230" 0 2 0.000000)
  (zti:tx "TEXT" 4555 867.5 35 "U2" 0 2 0.000000)
  (zti:tx "TEXT" 4785 867.5 35 "UM\\U+00DDVADIELKO 450 (len SV)" 0 2 0.000000)
  (zti:tx "TEXT" 6055 867.5 35 "20\\U+00D72,8" 0 2 0.000000)
  (zti:tx "TEXT" 6505 867.5 35 "\\U+2014" 0 2 0.000000)
  (zti:tx "TEXT" 6955 867.5 35 "DN50" 0 2 0.000000)
  (zti:tx "TEXT" 7405 867.5 35 "SV +550, K +500" 0 2 0.000000)
  (zti:tx "TEXT" 4525 685 40 "1. Vn\\U+00FAtorn\\U+00FD vodovod pod\\U+013Ea STN EN 806 a STN 73 6660, potrubie PPR PN20, spoje polyf\\U+00FAzne. Rozvody v dr\\U+00E1\\U+017Ekach / v predstene pod obkladom." 0 0 0.000000)
  (zti:tx "TEXT" 4525 603 40 "2. Pr\\U+00EDpojky od st\\U+00FApa\\U+010Diek DN20 = PPR 25\\U+00D73,5, pripojovacie potrubie k predmetom DN15 = PPR 20\\U+00D72,8." 0 0 0.000000)
  (zti:tx "TEXT" 4525 521 40 "3. SV izolova\\U+0165 proti orosovaniu, TV tepelne izolova\\U+0165 (hr\\U+00FAbka izol\\U+00E1cie pod\\U+013Ea platn\\U+00FDch predpisov)." 0 0 0.000000)
  (zti:tx "TEXT" 4525 439 40 "4. Vn\\U+00FAtorn\\U+00E1 kanaliz\\U+00E1cia pod\\U+013Ea STN EN 12056 a STN 73 6760, PP-HT, hrdlov\\U+00E9 spoje s tesnen\\U+00EDm. Sp\\U+00E1d DN50 min. 2 %, DN100 min. 1 % (navrhnut\\U+00E9 2 %)." 0 0 0.000000)
  (zti:tx "TEXT" 4525 357 40 "5. Vodovod vies\\U+0165 nad kanaliz\\U+00E1ciou. V predstienke a pri \\U+0161achte sa SV/TV kri\\U+017Euj\\U+00FA s K \\U+2013 dodr\\U+017Ea\\U+0165 v\\U+00FD\\U+0161kov\\U+00E9 odsadenie." 0 0 0.000000)
  (zti:tx "TEXT" 4525 275 40 "6. Napojenie na exist. st\\U+00FApa\\U+010Dky SV / TV / C a K1 DN100 v \\U+0161achte \\U+01601 \\U+2013 pred realiz\\U+00E1ciou overi\\U+0165 stav, materi\\U+00E1l a dimenzie." 0 0 0.000000)
  (zti:tx "TEXT" 4525 193 40 "7. V \\U+0161achte gu\\U+013Eov\\U+00E9 uz\\U+00E1very a bytov\\U+00E9 vodomery SV, TV (overi\\U+0165 so spr\\U+00E1vcom budovy). RD min. 300\\U+00D7300 zo strany WC." 0 0 0.000000)
  (zti:tx "TEXT" 4525 111 40 "8. Pred zakryt\\U+00EDm tlakov\\U+00E1 sk\\U+00FA\\U+0161ka vodovodu (STN EN 806-4), preplach a dezinfekcia; sk\\U+00FA\\U+0161ka tesnosti kanaliz\\U+00E1cie." 0 0 0.000000)
  (zti:tx "TEXT" 4525 29 40 "9. Pr\\U+00E1\\U+010Dka pred predstienkou, PV a ZS v predstienke za pr\\U+00E1\\U+010Dkou. V\\U+00FD\\U+0161ky v\\U+00FDvodov overi\\U+0165 pod\\U+013Ea zvolen\\U+00FDch v\\U+00FDrobkov." 0 0 0.000000)
  (zti:tx "TEXT" 4525 -53 40 "10. Um\\U+00FDvadielko U2 vo WC \\U+2013 pripojenie len na SV (v\\U+00FDtokov\\U+00FD ventil / bat\\U+00E9ria na SV) a K DN50, bez TV (ods\\U+00FAhlasen\\U+00E9 investorom)." 0 0 0.000000)
  (zti:tx "TEXT" 4525 -135 40 "11. V, PR a U1 \\U+2013 SPOLO\\U+010CN\\U+00C9 odpadov\\U+00E9 potrubie K DN50: pod va\\U+0148ou za obkladovou stienkou, v predstienke SDK (h 1200) za obkladom," 0 0 0.000000)
  (zti:tx "TEXT" 4525 -217 40 "     prierazom P1 \\U+00D880 v prie\\U+010Dke do WC, vo WC nad podlahou v obkladovom boxe 120\\U+00D7150, prierazom P2 \\U+00D880 pod RD do \\U+0161achty \\U+01601," 0 0 0.000000)
  (zti:tx "TEXT" 4525 -299 40 "     na K1 novou odbo\\U+010Dkou DN100/50 45\\U+00B0. Os: odtok V +130, P1 +77, K1 +58. Za\\U+00FAstenia PR a U1 odbo\\U+010Dkami 45\\U+00B0," 0 0 0.000000)
  (zti:tx "TEXT" 4525 -381 40 "     pri P1 \\U+010Distiaci kus s rev\\U+00EDznym otvorom v obklade. Predmety maj\\U+00FA vlastn\\U+00E9 z\\U+00E1pachov\\U+00E9 uz\\U+00E1vierky; vetranie cez K1." 0 0 0.000000)
  (zti:tx "TEXT" 4525 -463 40 "12. Va\\U+0148a skr\\U+00E1ten\\U+00E1 zo zadan\\U+00FDch 1700 na 1600\\U+00D7700 kv\\U+00F4li in\\U+0161tala\\U+010Dnej predstienke (ods\\U+00FAhlasen\\U+00E9 investorom)." 0 0 0.000000)
)
(defun zti:koty ()
  (setvar "CLAYER" "KOTY")
  (zti:dim -150 2250 0 2250 -75 2800 "_H")
  (zti:dim 0 2250 2400 2250 1200 2800 "_H")
  (zti:dim 2400 2250 2500 2250 2450 2800 "_H")
  (zti:dim 2500 2250 3700 2250 3100 2800 "_H")
  (zti:dim 3700 2250 3850 2250 3775 2800 "_H")
  (zti:dim -150 2250 3850 2250 1850 3050 "_H")
  (zti:dim 0 2100 1600 2100 800 2550 "_H")
  (zti:dim 1600 2100 2260 2100 1930 2550 "_H")
  (zti:dim 2260 2100 2400 2100 2330 2550 "_H")
  (zti:dim 2500 2100 2800 2100 2650 2550 "_H")
  (zti:dim 2800 2100 3275 2100 3037.5 2550 "_H")
  (zti:dim 3275 2100 3700 2100 3487.5 2550 "_H")
  (zti:dim 0 0 0 1400 -500 700 "_V")
  (zti:dim 0 1400 0 2100 -500 1750 "_V")
  (zti:dim -150 -100 -150 0 -800 -50 "_V")
  (zti:dim -150 0 -150 2100 -800 1050 "_V")
  (zti:dim -150 2100 -150 2250 -800 2175 "_V")
  (zti:dim 3700 500 3700 625 4150 562.5 "_V")
  (zti:dim 3700 625 3700 850 4150 737.5 "_V")
  (zti:dim 3700 850 3700 1075 4150 962.5 "_V")
  (zti:dim 3700 1075 3700 1850 4150 1462.5 "_V")
  (zti:dim 3700 1850 3700 2100 4150 1975 "_V")
  (zti:dim 3850 400 3850 2250 4400 1325 "_V")
  (zti:dim 1850 0 1850 700 1750 350 "_V")
  (zti:dim 1850 700 1850 1000 1750 850 "_V")
  (zti:dim 1850 1000 1850 1300 1750 1150 "_V")
  (zti:dim 0 0 300 0 150 200 "_H")
  (zti:dim 300 0 1000 0 650 200 "_H")
  (zti:dim 1000 0 2400 0 1700 200 "_H")
  (zti:dim 2500 500 2650 500 2575 580 "_H")
  (zti:dim 2650 500 3250 500 2950 580 "_H")
)

(defun zti:kresli (ox oy / old)
  (vl-load-com)
  (setq zti:ox ox zti:oy oy zti:err 0)
  (setq old (mapcar (quote getvar) (quote ("CMDECHO" "OSMODE" "CLAYER" "HPNAME" "ORTHOMODE"))))
  (setvar "CMDECHO" 0)
  (command "_.UNDO" "_BE")
  (command "_.UCS" "_W")
  (setvar "OSMODE" 0)
  (setvar "ORTHOMODE" 0)
  (zti:setup)
  (zti:cast0) (zti:cast1)
  (zti:koty)
  (setvar "CLAYER" (nth 2 old))
  (setvar "HPNAME" (nth 3 old))
  (command "_.UCS" "_P")
  (command "_.UNDO" "_E")
  (setvar "OSMODE" (nth 1 old))
  (setvar "ORTHOMODE" (nth 4 old))
  (setvar "CMDECHO" (nth 0 old))
  (command "_.ZOOM" "_E")
  (princ (strcat "\nZTI-01 nakreslene. Neuspesnych entmake: " (itoa zti:err)))
  zti:err)

(defun c:ZTI (/ u p)
  (setq u (getvar "INSUNITS"))
  (if (and (/= u 4)
           (/= "Ano" (progn (initget "Ano Nie")
                            (getkword (strcat "\nINSUNITS = " (itoa u)
                                              " (nie mm). Skript kresli v mm. Pokracovat? [Ano/Nie] <Nie>: ")))))
    (progn (princ "\nPreruseny - nastav INSUNITS na 4 (mm).") (exit)))
  (setq p (getpoint "\nBod vlozenia (lavy predny vnutorny roh kupelne) <0,0>: "))
  (if (not p) (setq p '(0.0 0.0 0.0)))
  (zti:kresli (car p) (cadr p))
  (princ))

(princ "\nZTI-01 nacitane. Spusti prikazom ZTI.")
(princ)
