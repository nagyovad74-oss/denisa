;;; ===========================================================================
;;; REKONSTRUKCIA BYTU - ZTI  |  PODORYS ROZVODOV VODY A KANALIZACIE  |  ZTI-01
;;; Vygenerovane skriptom zti/generuj_vykres.py - needitovat rucne.
;;;
;;; Pouzitie v AutoCADe:
;;;   1. APPLOAD -> nacitat tento subor (alebo pretiahnut do okna AutoCADu)
;;;   2. prikaz ZTI -> zadat bod vlozenia (Enter = 0,0)
;;;   Vysledok sa da vratit jednym Ctrl+Z (UNDO skupina). Vykres sa neuklada.
;;;   Z MCP servera / run_lisp:  (zti:kresli 0.0 0.0)
;;;
;;; Jednotky: mm (INSUNITS = 4). Tlac v M 1:25 na A3.
;;; ===========================================================================

(defun zti:p (x y) (list (+ x zti:ox) (+ y zti:oy) 0.0))
(defun zti:p2 (x y) (list (+ x zti:ox) (+ y zti:oy)))
(defun zti:em (lst) (if (not (entmake lst)) (setq zti:err (1+ zti:err))))

(defun zti:pl (lay vs cl pr)
  (zti:em
    (append
      (list '(0 . "LWPOLYLINE") '(100 . "AcDbEntity") (cons 8 lay))
      pr
      (list '(100 . "AcDbPolyline") (cons 90 (length vs)) (cons 70 cl))
      (apply 'append
        (mapcar '(lambda (v)
                   (list (cons 10 (zti:p2 (car v) (cadr v)))
                         (cons 40 (nth 3 v)) (cons 41 (nth 4 v)) (cons 42 (nth 2 v))))
                vs)))))

(defun zti:tx (lay x y h s hj vj rot / p)
  (setq p (zti:p x y))
  (zti:em
    (list '(0 . "TEXT") '(100 . "AcDbEntity") (cons 8 lay) '(100 . "AcDbText")
          (cons 10 p) (cons 40 h) (cons 1 s) (cons 50 rot) (cons 7 "ZTI")
          (cons 72 hj) (cons 11 p) '(100 . "AcDbText") (cons 73 vj))))

(defun zti:hatch (lay pts col / n edges e b)
  (setq n (length pts) edges '())
  (setq e
    (entmake
      (append
        (list '(0 . "HATCH") '(100 . "AcDbEntity") (cons 8 lay) (cons 62 col)
              '(100 . "AcDbHatch") '(10 0.0 0.0 0.0) '(210 0.0 0.0 1.0)
              '(2 . "SOLID") '(70 . 1) '(71 . 0) '(91 . 1) '(92 . 1) (cons 93 n))
        (apply 'append
          (mapcar '(lambda (a b)
                     (list '(72 . 1) (cons 10 (zti:p2 (car a) (cadr a))) (cons 11 (zti:p2 (car b) (cadr b)))))
                  pts (append (cdr pts) (list (car pts)))))
        (list '(97 . 0) '(75 . 0) '(76 . 1) '(98 . 1) (cons 10 (zti:p2 (caar pts) (cadar pts)))))))
  ;; nahradne riesenie, ak entmake HATCH zlyha: hranica + -HATCH
  (if (not e)
    (progn
      (zti:pl lay (mapcar '(lambda (p) (list (car p) (cadr p) 0.0 0.0 0.0)) pts) 1 nil)
      (setq b (entlast))
      (setvar "HPNAME" "SOLID")
      (command "_.-HATCH" "_S" b "" "")
      (if (not (eq (entlast) b))
        (progn (command "_.CHPROP" (entlast) "" "_LA" lay "_C" (itoa col) "")
               (entdel b) (setq e (entlast)))
        (setq zti:err (1+ zti:err)))))
  e)

(defun zti:dim (x1 y1 x2 y2 bx by dir)
  (command "_.DIMLINEAR" "_non" (zti:p x1 y1) "_non" (zti:p x2 y2) dir "_non" (zti:p bx by)))

(defun zti:layer (name col lw lt desc)
  (if (not (tblsearch "LAYER" name))
    (command "_.-LAYER" "_N" name ""))
  (command "_.-LAYER" "_C" (itoa col) name "_LT" lt name "_LW" lw name "")
  (if (and (tblsearch "LAYER" name) (vlax-get-acad-object))
    (vl-catch-all-apply
      '(lambda ()
         (vla-put-Description
           (vla-item (vla-get-Layers (vla-get-ActiveDocument (vlax-get-acad-object))) name)
           desc)))))

(defun zti:setup ()
  ;; textovy styl
  (if (not (tblsearch "STYLE" "ZTI"))
    (entmake '((0 . "STYLE") (100 . "AcDbSymbolTableRecord") (100 . "AcDbTextStyleTableRecord")
               (2 . "ZTI") (70 . 0) (40 . 0.0) (41 . 1.0) (50 . 0.0) (71 . 0) (42 . 2.5)
               (3 . "arial.ttf") (4 . ""))))
  ;; typy ciar vody: SV bodkociarkovana, TV dvojbodkociarkovana (vzor v mm na papieri)
  (if (not (tblsearch "LTYPE" "ZTI_BODKOCIARA"))
    (entmake '((0 . "LTYPE") (100 . "AcDbSymbolTableRecord") (100 . "AcDbLinetypeTableRecord")
               (2 . "ZTI_BODKOCIARA") (70 . 0) (3 . "SV ____ . ____ .") (72 . 65) (73 . 4) (40 . 11.0)
               (49 . 8.0) (74 . 0) (49 . -1.5) (74 . 0) (49 . 0.0) (74 . 0) (49 . -1.5) (74 . 0))))
  (if (not (tblsearch "LTYPE" "ZTI_DVOJBODKOCIARA"))
    (entmake '((0 . "LTYPE") (100 . "AcDbSymbolTableRecord") (100 . "AcDbLinetypeTableRecord")
               (2 . "ZTI_DVOJBODKOCIARA") (70 . 0) (3 . "TV ____ . . ____") (72 . 65) (73 . 6) (40 . 12.5)
               (49 . 8.0) (74 . 0) (49 . -1.5) (74 . 0) (49 . 0.0) (74 . 0) (49 . -1.5) (74 . 0)
               (49 . 0.0) (74 . 0) (49 . -1.5) (74 . 0))))

  (zti:layer "ZTI_KANALIZACIA_SCHEMA" 1 "0.50" "Continuous" "ZTI - schema kanalizacie")
  (zti:layer "ST_STAVBA" 7 "0.50" "Continuous" "Stavebna cast")
  (zti:layer "TEXT" 7 "0.25" "Continuous" "Texty a popisy")
  (zti:layer "RAM" 7 "0.50" "Continuous" "Ram a popisove pole")

  ;; koty - styl ZTI_25 (M 1:25, sikme znacky)
  (foreach v '(("DIMSCALE" 25.0) ("DIMTXT" 1.8) ("DIMASZ" 1.5) ("DIMTSZ" 1.2) ("DIMEXE" 1.5)
               ("DIMEXO" 1.0) ("DIMGAP" 0.6) ("DIMDLE" 1.2) ("DIMDEC" 0) ("DIMTAD" 1)
               ("DIMTIH" 0) ("DIMTOH" 0) ("DIMLUNIT" 2) ("DIMZIN" 8) ("DIMATFIT" 3) ("DIMTMOVE" 0))
    (setvar (car v) (cadr v)))
  (setvar "DIMTXSTY" "ZTI")
  (if (tblsearch "DIMSTYLE" "ZTI_25")
    (command "_.-DIMSTYLE" "_S" "ZTI_25" "_Y")
    (command "_.-DIMSTYLE" "_S" "ZTI_25"))
)

(defun zks:cast0 ()
  (zti:hatch "ST_STAVBA" (list '(10250 1125) '(18289.625 1125) '(18289.625 1525) '(10250 1525)) 253)
  (zti:pl "ST_STAVBA" (list '(10250 1125 0 0 0) '(18289.625 1125 0 0 0) '(18289.625 1525 0 0 0) '(10250 1525 0 0 0)) 1 (list (cons 370 35)))
  (zti:tx "TEXT" 10300 1575 50 "\\U+00B10,000 = \\U+010Dist\\U+00E1 podlaha" 0 0 0.000000)
  (zti:tx "TEXT" 10300 1200 40 "stropn\\U+00E1 doska (exist.)" 0 0 0.000000)
  (zti:hatch "ST_STAVBA" (list '(14228.75 1525) '(14341.25 1525) '(14341.25 2725) '(14228.75 2725)) 253)
  (zti:pl "ST_STAVBA" (list '(14228.75 1525 0 0 0) '(14341.25 1525 0 0 0) '(14341.25 2725 0 0 0) '(14228.75 2725 0 0 0)) 1 (list (cons 370 25)))
  (zti:tx "TEXT" 14285 2775 40 "P1 \\U+00D880" 1 0 0.000000)
  (zti:hatch "ST_STAVBA" (list '(15196.25 1525) '(15252.5 1525) '(15252.5 2725) '(15196.25 2725)) 253)
  (zti:pl "ST_STAVBA" (list '(15196.25 1525 0 0 0) '(15252.5 1525 0 0 0) '(15252.5 2725 0 0 0) '(15196.25 2725 0 0 0)) 1 (list (cons 370 25)))
  (zti:tx "TEXT" 15224.375 2775 40 "P2 \\U+00D880" 1 0 0.000000)
  (zti:hatch "ST_STAVBA" (list '(15694.625 1525) '(15750.875 1525) '(15750.875 2725) '(15694.625 2725)) 253)
  (zti:pl "ST_STAVBA" (list '(15694.625 1525 0 0 0) '(15750.875 1525 0 0 0) '(15750.875 2725 0 0 0) '(15694.625 2725 0 0 0)) 1 (list (cons 370 25)))
  (zti:tx "TEXT" 12867.5 4100 62.5 "1.01 K\\U+00DAPE\\U+013D\\U+0147A" 1 0 0.000000)
  (zti:tx "TEXT" 14754.688 3950 50 "1.02 WC" 1 0 0.000000)
  (zti:tx "TEXT" 17109.312 4100 62.5 "1.02 WC" 1 0 0.000000)
  (zti:tx "TEXT" 15615.75 4100 62.5 "\\U+01601" 0 0 0.000000)
  (zti:pl "ZTI_KANALIZACIA_SCHEMA" (list '(15515.75 875 0 0 0) '(15515.75 4300 0 0 0)) 0 (list (cons 370 70)))
  (zti:pl "ZTI_KANALIZACIA_SCHEMA" (list '(15440.75 4300 0 0 0) '(15490.75 4337.5 0 0 0) '(15540.75 4262.5 0 0 0) '(15590.75 4300 0 0 0)) 0 (list (cons 370 35)))
  (zti:pl "ZTI_KANALIZACIA_SCHEMA" (list '(15440.75 875 0 0 0) '(15490.75 912.5 0 0 0) '(15540.75 837.5 0 0 0) '(15590.75 875 0 0 0)) 0 (list (cons 370 35)))
  (zti:tx "TEXT" 15553.25 4400 40 "\\U+2191 vetranie nad strechu (exist.)" 0 0 0.000000)
  (zti:tx "TEXT" 15553.25 775 40 "\\U+2193 zvodov\\U+00E9 potrubie (exist.)" 0 0 0.000000)
  (zti:tx "TEXT" 15465.75 2925 50 "K1 \\U+2013 DN100 PP-HT (exist.)" 0 0 1.570796)
  (zti:pl "ZTI_KANALIZACIA_SCHEMA" (list '(11450 1980 0 0 0) '(15440.75 1727.02 0 0 0) '(15515.75 1652.02 0 0 0)) 0 (list))
  (zti:pl "ST_STAVBA" (list '(10700 2120 0 0 0) '(11500 2120 0 0 0) '(11500 3485 0 0 0) '(10700 3485 0 0 0)) 1 (list (cons 370 25)))
  (zti:tx "TEXT" 11100 2855 75 "V" 1 2 0.000000)
  (zti:pl "ZTI_KANALIZACIA_SCHEMA" (list '(11450 2120 0 0 0) '(11450 1980 0 0 0)) 0 (list))
  (zti:tx "TEXT" 10725 2032.5 37.5 "va\\U+0148ov\\U+00FD sif\\U+00F3n DN50" 0 0 0.000000)
  (zti:pl "ZTI_KANALIZACIA_SCHEMA" (list '(13445 3975 0 0 0) '(13445 1926.2 0 0 0) '(13520 1851.2 0 0 0)) 0 (list))
  (zti:em (list '(0 . "CIRCLE") (cons 8 "ZTI_KANALIZACIA_SCHEMA") (cons 10 (zti:p 13445 4005)) (cons 40 30)))
  (zti:tx "TEXT" 13445 4075 75 "PR" 1 0 0.000000)
  (zti:tx "TEXT" 13490 3912.5 37.5 "ZS pr\\U+00E1\\U+010Dky +700" 0 0 0.000000)
  (zti:tx "TEXT" 13540 1913.7 35 "odb. 45\\U+00B0" 0 0 0.000000)
  (zti:pl "ZTI_KANALIZACIA_SCHEMA" (list '(14120 3275 0 0 0) '(14120 1884.2 0 0 0) '(14195 1809.2 0 0 0)) 0 (list))
  (zti:em (list '(0 . "CIRCLE") (cons 8 "ZTI_KANALIZACIA_SCHEMA") (cons 10 (zti:p 14120 3305)) (cons 40 30)))
  (zti:tx "TEXT" 14120 3375 75 "U1" 1 0 0.000000)
  (zti:tx "TEXT" 14165 3212.5 37.5 "sif\\U+00F3n um\\U+00FDvadla +500" 0 0 0.000000)
  (zti:tx "TEXT" 14215 1871.7 35 "odb. 45\\U+00B0" 0 0 0.000000)
  (zti:pl "ZTI_KANALIZACIA_SCHEMA" (list '(14347.5 1759.878 0 0 0) '(14422.5 1759.878 0 0 0) '(14422.5 1834.878 0 0 0) '(14347.5 1834.878 0 0 0)) 1 (list (cons 370 25)))
  (zti:tx "TEXT" 14385 1672.378 35 "\\U+010CK DN50" 1 0 0.000000)
  (zti:tx "TEXT" 14754.688 1397.5 35 "v obkladovom boxe 120\\U+00D7150" 1 0 0.000000)
  (zti:pl "ZTI_KANALIZACIA_SCHEMA" (list '(16229 2330 0 0 0) '(15590.75 2285.62 0 0 0) '(15515.75 2210.62 0 0 0)) 0 (list (cons 370 70)))
  (zti:pl "ST_STAVBA" (list '(16204 2575 0 0 0) '(16554 2575 0 0 0) '(16554 2995 0 0 0) '(16204 2995 0 0 0)) 1 (list (cons 370 25)))
  (zti:pl "ST_STAVBA" (list '(16204 2085 0 0 0) '(16204 3800 0 0 0)) 0 (list (cons 370 25)))
  (zti:tx "TEXT" 16379 2785 75 "WC" 1 2 0.000000)
  (zti:pl "ZTI_KANALIZACIA_SCHEMA" (list '(16254 2575 0 0 0) '(16229 2330 0 0 0)) 0 (list (cons 370 70)))
  (zti:tx "TEXT" 16379 2500 35 "modul v predstene" 1 0 0.000000)
  (zti:pl "ZTI_KANALIZACIA_SCHEMA" (list '(17989.625 3275 0 0 0) '(17989.625 2505 0 0 0) '(16304 2395.45 0 0 0) '(16229 2320.45 0 0 0)) 0 (list))
  (zti:em (list '(0 . "CIRCLE") (cons 8 "ZTI_KANALIZACIA_SCHEMA") (cons 10 (zti:p 17989.625 3305)) (cons 40 30)))
  (zti:tx "TEXT" 17989.625 3375 75 "U2" 1 0 0.000000)
  (zti:tx "TEXT" 17944.625 3212.5 37.5 "sif\\U+00F3n +500" 2 0 0.000000)
  (zti:tx "TEXT" 16249 2457.95 35 "odb. 45\\U+00B0" 0 0 0.000000)
  (zti:tx "TEXT" 15553.25 2135.62 35 "odb. DN100/100 45\\U+00B0" 0 0 0.000000)
  (zti:tx "TEXT" 15478.25 1577.02 35 "nov\\U+00E1 odb. DN100/50 45\\U+00B0" 2 0 0.000000)
  (zti:tx "TEXT" 12485 1960.6 45 "DN50, i = 2 %" 1 0 -0.062142)
  (zti:tx "TEXT" 14709.688 1822.175 45 "DN50, i = 2 %" 1 0 -0.062142)
  (zti:tx "TEXT" 15872.375 2352.81 45 "DN100, i = 2 %" 1 0 0.062142)
  (zti:tx "TEXT" 17109.312 2495.225 45 "DN50, i = 2 %" 1 0 0.062142)
  (zti:pl "TEXT" (list '(11450 1980 0 0 0) '(11420 2030 0 0 0) '(11480 2030 0 0 0)) 1 (list (cons 370 18)))
  (zti:tx "TEXT" 11490 2045 37.5 "+130" 0 0 0.000000)
  (zti:pl "TEXT" (list '(13520 1851.2 0 0 0) '(13490 1901.2 0 0 0) '(13550 1901.2 0 0 0)) 1 (list (cons 370 18)))
  (zti:tx "TEXT" 13560 1916.2 37.5 "+93" 0 0 0.000000)
  (zti:pl "TEXT" (list '(14195 1809.2 0 0 0) '(14165 1859.2 0 0 0) '(14225 1859.2 0 0 0)) 1 (list (cons 370 18)))
  (zti:tx "TEXT" 14235 1874.2 37.5 "+81" 0 0 0.000000)
  (zti:pl "TEXT" (list '(15224.375 1745.15 0 0 0) '(15194.375 1795.15 0 0 0) '(15254.375 1795.15 0 0 0)) 1 (list (cons 370 18)))
  (zti:tx "TEXT" 15184.375 1810.15 37.5 "+63" 2 0 0.000000)
  (zti:pl "TEXT" (list '(15440.75 1727.02 0 0 0) '(15410.75 1777.02 0 0 0) '(15470.75 1777.02 0 0 0)) 1 (list (cons 370 18)))
  (zti:tx "TEXT" 15400.75 1792.02 37.5 "+58" 2 0 0.000000)
  (zti:pl "TEXT" (list '(16229 2330 0 0 0) '(16199 2380 0 0 0) '(16259 2380 0 0 0)) 1 (list (cons 370 18)))
  (zti:tx "TEXT" 16269 2395 37.5 "+230" 0 0 0.000000)
  (zti:pl "TEXT" (list '(15590.75 2285.62 0 0 0) '(15560.75 2335.62 0 0 0) '(15620.75 2335.62 0 0 0)) 1 (list (cons 370 18)))
  (zti:tx "TEXT" 15630.75 2350.62 37.5 "+217" 0 0 0.000000)
  (zti:pl "TEXT" (list '(17989.625 2505 0 0 0) '(17959.625 2555 0 0 0) '(18019.625 2555 0 0 0)) 1 (list (cons 370 18)))
  (zti:tx "TEXT" 17949.625 2570 37.5 "+280" 2 0 0.000000)
  (zti:pl "TEXT" (list '(10125 700 0 0 0) '(18139.625 700 0 0 0)) 0 (list (cons 370 35)))
  (zti:pl "TEXT" (list '(10125 525 0 0 0) '(18139.625 525 0 0 0)) 0 (list (cons 370 18)))
  (zti:pl "TEXT" (list '(10125 350 0 0 0) '(18139.625 350 0 0 0)) 0 (list (cons 370 18)))
  (zti:pl "TEXT" (list '(10125 175 0 0 0) '(18139.625 175 0 0 0)) 0 (list (cons 370 18)))
  (zti:pl "TEXT" (list '(10125 0 0 0 0) '(18139.625 0 0 0 0)) 0 (list (cons 370 18)))
  (zti:pl "TEXT" (list '(10125 -175 0 0 0) '(18139.625 -175 0 0 0)) 0 (list (cons 370 18)))
  (zti:pl "TEXT" (list '(10125 -525 0 0 0) '(18139.625 -525 0 0 0)) 0 (list (cons 370 35)))
  (zti:pl "TEXT" (list '(10125 700 0 0 0) '(10125 -525 0 0 0)) 0 (list (cons 370 35)))
  (zti:pl "TEXT" (list '(11350 700 0 0 0) '(11350 -525 0 0 0)) 0 (list (cons 370 18)))
  (zti:pl "TEXT" (list '(11450 700 0 0 0) '(11450 -525 0 0 0)) 0 (list (cons 370 18)))
  (zti:pl "TEXT" (list '(13520 700 0 0 0) '(13520 -525 0 0 0)) 0 (list (cons 370 18)))
  (zti:pl "TEXT" (list '(14195 700 0 0 0) '(14195 -525 0 0 0)) 0 (list (cons 370 18)))
  (zti:pl "TEXT" (list '(15224.375 700 0 0 0) '(15224.375 -525 0 0 0)) 0 (list (cons 370 18)))
  (zti:pl "TEXT" (list '(15515.75 700 0 0 0) '(15515.75 -525 0 0 0)) 0 (list (cons 370 18)))
  (zti:pl "TEXT" (list '(16229 700 0 0 0) '(16229 -525 0 0 0)) 0 (list (cons 370 18)))
  (zti:pl "TEXT" (list '(17989.625 700 0 0 0) '(17989.625 -525 0 0 0)) 0 (list (cons 370 18)))
  (zti:pl "TEXT" (list '(18139.625 700 0 0 0) '(18139.625 -525 0 0 0)) 0 (list (cons 370 35)))
  (zti:tx "TEXT" 10162.5 612.5 40 "\\U+00DASEK" 0 2 0.000000)
  (zti:tx "TEXT" 10162.5 437.5 40 "MATERI\\U+00C1L" 0 2 0.000000)
  (zti:tx "TEXT" 10162.5 262.5 40 "DN" 0 2 0.000000)
  (zti:tx "TEXT" 10162.5 87.5 40 "D\\U+0139\\U+017DKA [m]" 0 2 0.000000)
  (zti:tx "TEXT" 10162.5 -87.5 40 "SP\\U+00C1D [%]" 0 2 0.000000)
  (zti:tx "TEXT" 10162.5 -350 40 "V\\U+00DD\\U+0160KA OSI [mm]" 0 2 0.000000)
  (zti:tx "TEXT" 12485 612.5 40 "V \\U+2013 PR" 1 2 0.000000)
  (zti:tx "TEXT" 12485 437.5 40 "PP-HT" 1 2 0.000000)
  (zti:tx "TEXT" 12485 262.5 40 "50" 1 2 0.000000)
  (zti:tx "TEXT" 12485 87.5 40 "1,84" 1 2 0.000000)
  (zti:tx "TEXT" 12485 -87.5 40 "2" 1 2 0.000000)
  (zti:tx "TEXT" 13857.5 612.5 40 "PR \\U+2013 U1" 1 2 0.000000)
  (zti:tx "TEXT" 13857.5 437.5 40 "PP-HT" 1 2 0.000000)
  (zti:tx "TEXT" 13857.5 262.5 40 "50" 1 2 0.000000)
  (zti:tx "TEXT" 13857.5 87.5 40 "0,60" 1 2 0.000000)
  (zti:tx "TEXT" 13857.5 -87.5 40 "2" 1 2 0.000000)
  (zti:tx "TEXT" 14709.688 612.5 40 "U1 \\U+2013 P2" 1 2 0.000000)
  (zti:tx "TEXT" 14709.688 437.5 40 "PP-HT" 1 2 0.000000)
  (zti:tx "TEXT" 14709.688 262.5 40 "50" 1 2 0.000000)
  (zti:tx "TEXT" 14709.688 87.5 40 "0,92" 1 2 0.000000)
  (zti:tx "TEXT" 14709.688 -87.5 40 "2" 1 2 0.000000)
  (zti:tx "TEXT" 15370.062 612.5 32.5 "P2\\U+2013K1" 1 2 1.570796)
  (zti:tx "TEXT" 15370.062 437.5 32.5 "PP-HT" 1 2 0.000000)
  (zti:tx "TEXT" 15370.062 262.5 32.5 "50" 1 2 0.000000)
  (zti:tx "TEXT" 15370.062 87.5 32.5 "0,26" 1 2 0.000000)
  (zti:tx "TEXT" 15370.062 -87.5 32.5 "2" 1 2 0.000000)
  (zti:tx "TEXT" 15872.375 612.5 40 "K1 \\U+2013 WC" 1 2 0.000000)
  (zti:tx "TEXT" 15872.375 437.5 40 "PP-HT" 1 2 0.000000)
  (zti:tx "TEXT" 15872.375 262.5 40 "100" 1 2 0.000000)
  (zti:tx "TEXT" 15872.375 87.5 40 "0,63" 1 2 0.000000)
  (zti:tx "TEXT" 15872.375 -87.5 40 "2" 1 2 0.000000)
  (zti:tx "TEXT" 17109.312 612.5 40 "WC \\U+2013 U2" 1 2 0.000000)
  (zti:tx "TEXT" 17109.312 437.5 40 "PP-HT" 1 2 0.000000)
  (zti:tx "TEXT" 17109.312 262.5 40 "50" 1 2 0.000000)
  (zti:tx "TEXT" 17109.312 87.5 40 "1,56" 1 2 0.000000)
  (zti:tx "TEXT" 17109.312 -87.5 40 "2" 1 2 0.000000)
  (zti:tx "TEXT" 11510 -350 37.5 "+130" 1 2 1.570796)
  (zti:tx "TEXT" 13580 -350 37.5 "+93" 1 2 1.570796)
  (zti:tx "TEXT" 14255 -350 37.5 "+81" 1 2 1.570796)
  (zti:tx "TEXT" 15284.375 -350 37.5 "+63" 1 2 1.570796)
  (zti:tx "TEXT" 15495.75 -350 37.5 "+58" 1 2 1.570796)
  (zti:tx "TEXT" 15575.75 -350 37.5 "+217" 1 2 1.570796)
  (zti:tx "TEXT" 16289 -350 37.5 "+230" 1 2 1.570796)
  (zti:tx "TEXT" 17969.625 -350 37.5 "+280" 1 2 1.570796)
  (zti:tx "TEXT" 10125 -700 87.5 "LEGENDA" 0 0 0.000000)
  (zti:pl "TEXT" (list '(10125 -737.5 0 0 0) '(12500 -737.5 0 0 0)) 0 (list (cons 370 35)))
  (zti:pl "ZTI_KANALIZACIA_SCHEMA" (list '(10125 -900 0 0 0) '(10625 -900 0 0 0)) 0 (list))
  (zti:tx "TEXT" 10725 -900 45 "kanaliza\\U+010Dn\\U+00E9 potrubie PP-HT DN50" 0 2 0.000000)
  (zti:pl "ZTI_KANALIZACIA_SCHEMA" (list '(10125 -1062.5 0 0 0) '(10625 -1062.5 0 0 0)) 0 (list (cons 370 70)))
  (zti:tx "TEXT" 10725 -1062.5 45 "kanaliza\\U+010Dn\\U+00E9 potrubie / st\\U+00FApa\\U+010Dka DN100" 0 2 0.000000)
  (zti:pl "ZTI_KANALIZACIA_SCHEMA" (list '(10125 -1225 0 0 0) '(10475 -1225 0 0 0) '(10550 -1150 0 0 0)) 0 (list))
  (zti:tx "TEXT" 10725 -1225 45 "odbo\\U+010Dka 45\\U+00B0" 0 2 0.000000)
  (zti:pl "ZTI_KANALIZACIA_SCHEMA" (list '(10125 -1387.5 0 0 0) '(10625 -1387.5 0 0 0)) 0 (list))
  (zti:pl "ZTI_KANALIZACIA_SCHEMA" (list '(10337.5 -1425 0 0 0) '(10412.5 -1425 0 0 0) '(10412.5 -1350 0 0 0) '(10337.5 -1350 0 0 0)) 1 (list (cons 370 25)))
  (zti:tx "TEXT" 10725 -1387.5 45 "\\U+010Distiaci kus s rev\\U+00EDznym otvorom (\\U+010CK)" 0 2 0.000000)
  (zti:em (list '(0 . "CIRCLE") (cons 8 "ZTI_KANALIZACIA_SCHEMA") (cons 10 (zti:p 10375 -1550)) (cons 40 30)))
  (zti:tx "TEXT" 10725 -1550 45 "z\\U+00E1pachov\\U+00E1 uz\\U+00E1vierka / sif\\U+00F3n" 0 2 0.000000)
  (zti:pl "TEXT" (list '(10375 -1737.5 0 0 0) '(10345 -1687.5 0 0 0) '(10405 -1687.5 0 0 0)) 1 (list (cons 370 18)))
  (zti:tx "TEXT" 10725 -1712.5 45 "v\\U+00FD\\U+0161ka osi potrubia od \\U+00B10,000 [mm]" 0 2 0.000000)
  (zti:hatch "ST_STAVBA" (list '(10325 -1925) '(10425 -1925) '(10425 -1825) '(10325 -1825)) 253)
)
(defun zks:cast1 ()
  (zti:pl "ST_STAVBA" (list '(10325 -1925 0 0 0) '(10425 -1925 0 0 0) '(10425 -1825 0 0 0) '(10325 -1825 0 0 0)) 1 (list (cons 370 25)))
  (zti:tx "TEXT" 10725 -1875 45 "stena / prieraz P1, P2" 0 2 0.000000)
  (zti:tx "TEXT" 12675 -700 87.5 "POZN\\U+00C1MKY" 0 0 0.000000)
  (zti:tx "TEXT" 12675 -835 42.5 "1. Sch\\U+00E9ma \\U+2013 rozvinut\\U+00FD rez, v\\U+00FD\\U+0161ky prev\\U+00FD\\U+0161en\\U+00E9 (vodorovne \\U+2248 1:22," 0 0 0.000000)
  (zti:tx "TEXT" 12675 -970 42.5 "    zvisle \\U+2248 1:7). Platia k\\U+00F3ty a \\U+00FAdaje v tabu\\U+013Eke." 0 0 0.000000)
  (zti:tx "TEXT" 12675 -1105 42.5 "2. Potrubie PP-HT, hrdlov\\U+00E9 spoje s tesnen\\U+00EDm, odbo\\U+010Dky 45\\U+00B0." 0 0 0.000000)
  (zti:tx "TEXT" 12675 -1240 42.5 "3. Sp\\U+00E1d pripojovacieho potrubia 2 % (DN50 min. 2 %," 0 0 0.000000)
  (zti:tx "TEXT" 12675 -1375 42.5 "    DN100 min. 1 %). V\\U+00FD\\U+0161ky osi od \\U+00B10,000 \\U+010Distej podlahy." 0 0 0.000000)
  (zti:tx "TEXT" 12675 -1510 42.5 "4. V, PR a U1 \\U+2013 spolo\\U+010Dn\\U+00E9 potrubie DN50 (pozri ZTI-01," 0 0 0.000000)
  (zti:tx "TEXT" 12675 -1645 42.5 "    pozn. 11); U2 za\\U+00FAsten\\U+00E9 do odpadu WC DN100." 0 0 0.000000)
  (zti:tx "TEXT" 12675 -1780 42.5 "5. Napojenie na exist. K1 novou odbo\\U+010Dkou \\U+2013 pred realiz\\U+00E1ciou" 0 0 0.000000)
  (zti:tx "TEXT" 12675 -1915 42.5 "    overi\\U+0165 materi\\U+00E1l a dimenziu st\\U+00FApa\\U+010Dky." 0 0 0.000000)
  (zti:tx "TEXT" 12675 -2050 42.5 "6. Pred zakryt\\U+00EDm sk\\U+00FA\\U+0161ka tesnosti kanaliz\\U+00E1cie." 0 0 0.000000)
  (zti:pl "RAM" (list '(9500 -2600 0 0 0) '(20000 -2600 0 0 0) '(20000 4825 0 0 0) '(9500 4825 0 0 0)) 1 (list (cons 370 18)))
  (zti:pl "RAM" (list '(10000 -2475 0 0 0) '(19875 -2475 0 0 0) '(19875 4700 0 0 0) '(10000 4700 0 0 0)) 1 (list (cons 370 50)))
  (zti:pl "RAM" (list '(15375 -2475 0 0 0) '(19875 -2475 0 0 0) '(19875 -1175 0 0 0) '(15375 -1175 0 0 0)) 1 (list (cons 370 50)))
  (zti:pl "RAM" (list '(15375 -2125 0 0 0) '(19875 -2125 0 0 0)) 0 (list (cons 370 35)))
  (zti:pl "RAM" (list '(15375 -1675 0 0 0) '(19875 -1675 0 0 0)) 0 (list (cons 370 35)))
  (zti:pl "RAM" (list '(15375 -1425 0 0 0) '(19875 -1425 0 0 0)) 0 (list (cons 370 35)))
  (zti:pl "RAM" (list '(17625 -1425 0 0 0) '(17625 -1175 0 0 0)) 0 (list (cons 370 18)))
  (zti:pl "RAM" (list '(17625 -1675 0 0 0) '(17625 -1425 0 0 0)) 0 (list (cons 370 18)))
  (zti:tx "TEXT" 15415 -2212.5 35 "STUPE\\U+0147" 0 0 0.000000)
  (zti:tx "TEXT" 15825 -2405 70 "\\U+2014" 1 0 0.000000)
  (zti:pl "RAM" (list '(16275 -2475 0 0 0) '(16275 -2125 0 0 0)) 0 (list (cons 370 18)))
  (zti:tx "TEXT" 16315 -2212.5 35 "MIERKA" 0 0 0.000000)
  (zti:tx "TEXT" 16725 -2405 70 "sch\\U+00E9ma" 1 0 0.000000)
  (zti:pl "RAM" (list '(17175 -2475 0 0 0) '(17175 -2125 0 0 0)) 0 (list (cons 370 18)))
  (zti:tx "TEXT" 17215 -2212.5 35 "FORM\\U+00C1T" 0 0 0.000000)
  (zti:tx "TEXT" 17625 -2405 70 "A3" 1 0 0.000000)
  (zti:pl "RAM" (list '(18075 -2475 0 0 0) '(18075 -2125 0 0 0)) 0 (list (cons 370 18)))
  (zti:tx "TEXT" 18115 -2212.5 35 "D\\U+00C1TUM" 0 0 0.000000)
  (zti:tx "TEXT" 18525 -2405 70 "10/2026" 1 0 0.000000)
  (zti:pl "RAM" (list '(18975 -2475 0 0 0) '(18975 -2125 0 0 0)) 0 (list (cons 370 18)))
  (zti:tx "TEXT" 19015 -2212.5 35 "\\U+010C. V\\U+00DDKRESU" 0 0 0.000000)
  (zti:tx "TEXT" 19425 -2405 70 "ZTI-02" 1 0 0.000000)
  (zti:tx "TEXT" 15435 -1862.5 125 "REKON\\U+0160TRUKCIA BYTU \\U+2013 ZTI" 0 0 0.000000)
  (zti:tx "TEXT" 15435 -2045 70 "SCH\\U+00C9MA KANALIZ\\U+00C1CIE \\U+2013 ROZVINUT\\U+00DD REZ" 0 0 0.000000)
  (zti:tx "TEXT" 15415 -1250 35 "INVESTOR" 0 0 0.000000)
  (zti:tx "TEXT" 15415 -1385 50 "\\U+2014 (doplni\\U+0165)" 0 0 0.000000)
  (zti:tx "TEXT" 17665 -1250 35 "MIESTO STAVBY" 0 0 0.000000)
  (zti:tx "TEXT" 17665 -1385 50 "3-izbov\\U+00FD byt \\U+2014 (adresa doplni\\U+0165)" 0 0 0.000000)
  (zti:tx "TEXT" 15415 -1500 35 "VYPRACOVALA" 0 0 0.000000)
  (zti:tx "TEXT" 15415 -1635 50 "\\U+2014" 0 0 0.000000)
  (zti:tx "TEXT" 17665 -1500 35 "ZODP. PROJEKTANT" 0 0 0.000000)
  (zti:tx "TEXT" 17665 -1635 50 "\\U+2014" 0 0 0.000000)
  (zti:tx "TEXT" 19835 -1635 35 "PROFESIA: ZTI" 2 0 0.000000)
  (zti:tx "TEXT" 10125 4550 112.5 "SCH\\U+00C9MA KANALIZ\\U+00C1CIE \\U+2013 K\\U+00DAPE\\U+013D\\U+0147A 1.01 A WC 1.02" 0 0 0.000000)
  (zti:pl "TEXT" (list '(10125 4500 0 0 0) '(14500 4500 0 0 0)) 0 (list (cons 370 50)))
)
(defun zks:koty ()
  (setvar "CLAYER" "KOTY")
)

(defun zks:kresli (ox oy / old)
  (vl-load-com)
  (setq zti:ox ox zti:oy oy zti:err 0)
  (setq old (mapcar (quote getvar) (quote ("CMDECHO" "OSMODE" "CLAYER" "HPNAME" "ORTHOMODE"))))
  (setvar "CMDECHO" 0)
  (command "_.UNDO" "_BE")
  (command "_.UCS" "_W")
  (setvar "OSMODE" 0)
  (setvar "ORTHOMODE" 0)
  (zti:setup)
  (zks:cast0) (zks:cast1)
  (zks:koty)
  (setvar "CLAYER" (nth 2 old))
  (setvar "HPNAME" (nth 3 old))
  (command "_.UCS" "_P")
  (command "_.UNDO" "_E")
  (setvar "OSMODE" (nth 1 old))
  (setvar "ORTHOMODE" (nth 4 old))
  (setvar "CMDECHO" (nth 0 old))
  (command "_.ZOOM" "_E")
  (princ (strcat "\nZTI-02 nakreslene. Neuspesnych entmake: " (itoa zti:err)))
  zti:err)

(defun c:ZTISCHEMA (/ u p)
  (setq u (getvar "INSUNITS"))
  (if (and (/= u 4)
           (/= "Ano" (progn (initget "Ano Nie")
                            (getkword (strcat "\nINSUNITS = " (itoa u)
                                              " (nie mm). Skript kresli v mm. Pokracovat? [Ano/Nie] <Nie>: ")))))
    (progn (princ "\nPreruseny - nastav INSUNITS na 4 (mm).") (exit)))
  (setq p (getpoint "\nBod vlozenia (lavy predny vnutorny roh kupelne) <0,0>: "))
  (if (not p) (setq p '(0.0 0.0 0.0)))
  (zks:kresli (car p) (cadr p))
  (princ))

(princ "\nZTI-02 nacitane. Spusti prikazom ZTISCHEMA.")
(princ)
